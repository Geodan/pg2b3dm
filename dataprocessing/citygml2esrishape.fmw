FME workspace citygml2esrishape.fmw

Parameters:
- DestDataset_ESRISHAPE = D:\aaa\multipatchshape\test.shp   # Destination Esri Shapefile Folder
- SourceDataset_CITYGML_3 = C:\Users\bertt\Desktop\LoD2_280_5657_1_NW.gml   # Source CityGML File(s)
- FEATURE_TYPES =

Readers:
- CITYGML_2: CITYGML from $(SourceDataset_CITYGML_3)

Writers:
- ESRISHAPE_1: ESRISHAPE to $(DestDataset_ESRISHAPE) in EPSG:25832

CityModel (reader CITYGML_2)
    attributes: citygml_target_uri xml_buffer, gml_description xml_buffer, gml_name xml_buffer, citygml_city_object_member{}.xlink_href xml_buffer, gml_feature_member{}.xlink_href xml_buffer, DatenquelleLage xml_buffer, citygml_feature_role_attr_val xml_buffer, BezugspunktDach xml_buffer, externalReference{}.externalObject.name xml_xml, citygml_creationDate xml_date, citygml_measured_height_units xml_buffer, citygml_storeys_below_ground xml_uint64, externalReference{}.informationSystem xml_xml, externalReference{}.externalObject.uri xml_xml, DatenquelleBodenhoehe xml_buffer, citygml_storeys_above_ground xml_uint64, citygml_address{}.xlink_href xml_buffer, citygml_function xml_buffer, citygml_consists_of_building_part{}.xlink_href xml_buffer, DatenquelleDachhoehe xml_buffer, Gemeindeschluessel xml_buffer, citygml_feature_role xml_buffer, citygml_measured_height xml_real64, citygml_terminationDate xml_date, citygml_feature_role_attr_name xml_buffer, citygml_address xml_xml, citygml_level_of_detail{} xml_buffer
    -> GeometryFilter
GeometryFilter
    BREAK_AGG = Yes
    GEOM_PORT_NAMES = Ellipse Raster Text Instance Line Point Area Arc "Point Cloud" Surface Solid Collection Null
    INSTANTIATE = No
    SOLID -> Triangulator
Triangulator
    DEAGGREGATE_INPUT = Deaggregate
    TRIANGLES -> ouput (writer ESRISHAPE_1)
ouput (writer ESRISHAPE_1)
    attributes: gml_id char(254), gml_name char(254)
